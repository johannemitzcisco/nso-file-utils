module nso-file-utils {

  namespace "http://example.com/nso-filetemplate";
  prefix nso-filetemplate;

  import ietf-inet-types {
    prefix inet;
  }
  import tailf-common {
    prefix tailf;
  }
  import tailf-ncs {
    prefix ncs;
  }

  description
    "NSO file utililities to support file based operations";

  revision 2021-08-27 {
    description
      "Initial revision.";
  }

  grouping generate-template-inputs {
    list variable {
      leaf name {
        type leafref {
          path "../../../variable";
        }
      }
      leaf value {
        type string;
      }
    }
  }

  list template {
    description "Datamodel to store template information";

    key name;
    leaf name {
      tailf:info "Name of the templates";
      tailf:cli-allow-range;
      type string;
    }

    leaf source {
      type string;
    }

    leaf-list variable {
      type string;
    }
    tailf:action generate-template {
      tailf:actionpoint generate-template;
      input {
        uses generate-template-inputs;
      }
      output {
        leaf result {
          type string;
        }
      }
    }
    tailf:action generate-template-to-file {
      tailf:actionpoint generate-template-to-file;
      input {
        uses generate-template-inputs;
        leaf output-filename {
          type string;
        }
        leaf overwrite {
          type boolean;
          default false;
        }
      }
      output {
        leaf result {
          type string;
        }
      }
    }
  }
}
